(setq *FX-SEAL* "04/10/26" *FX-REV* "B"
      *FX-LOG* "C:/RevitAddinDev/CIVIL 3D_MCP Setup/tb_batch/tb_fix_log.csv")
(defun fx:find-last (pat s / i m r)
  (setq m (strlen pat) i (- (strlen s) m -1))
  (while (and (not r) (>= i 1))
    (if (= (substr s i m) pat) (setq r i))
    (setq i (1- i)))
  r)
(defun fx:repl-last (s old new / i)
  (if (setq i (fx:find-last old s))
    (strcat (substr s 1 (1- i)) new (substr s (+ i (strlen old))))
    nil))
(defun fx:settext (e new / ed)
  (setq ed (entget e))
  (entmod (subst (cons 1 new) (assoc 1 ed) ed))
  (entupd e))
(defun fx:sealpos (o)
  (or (and (< (abs (- (nth 3 o) 1029.03)) 1.0) (< (abs (- (nth 4 o) 64.56)) 1.0))
      (and (< (abs (- (nth 3 o) 582.73)) 1.0) (< (abs (- (nth 4 o) 201.33)) 1.0))))
(defun c:TBFIX (/ r dn out ns nr no nd new f *error*)
  (defun *error* (msg / ef)
    (if (setq ef (open *FX-LOG* "a"))
      (progn (write-line (strcat (getvar "DWGNAME") ",LISP_ERROR " msg) ef) (close ef)))
    (princ))
  (setq r (au:classify) dn (car r) out (caddr r) ns 0 nr 0 no 0 nd 0)
  (foreach o out
    (cond
      ((or (= (car o) "SEALDATE") (and (= (car o) "OTHERDATE") (fx:sealpos o)))
       (if (/= (nth 2 o) *FX-SEAL*)
         (progn
           (setq new (fx:repl-last (nth 7 o) (nth 2 o) *FX-SEAL*))
           (fx:settext (nth 1 o) (if new new *FX-SEAL*))
           (setq ns (1+ ns)))))
      ((= (car o) "REVNO")
       (if (/= (nth 2 o) *FX-REV*)
         (progn
           (setq new (fx:repl-last (nth 7 o) (nth 2 o) *FX-REV*))
           (fx:settext (nth 1 o) (if new new *FX-REV*))
           (setq nr (1+ nr)))))
      ((and (= (car o) "REVROW_OVERLAY") (= (nth 6 o) "PS"))
       (entdel (nth 1 o))
       (setq no (1+ no)))))
  (if (and dn (wcmatch (nth 1 dn) "NC-CQT-*-DWG-LI-*-@"))
    (progn
      (setq new (fx:repl-last (nth 6 dn) (strcat "-" (substr (nth 1 dn) (strlen (nth 1 dn)))) ""))
      (if new (progn (fx:settext (car dn) new) (setq nd 1)))))
  (if (setq f (open *FX-LOG* "a"))
    (progn
      (write-line (strcat (getvar "DWGNAME") ",SEAL=" (itoa ns) " REVNO=" (itoa nr) " OVERLAY_DEL=" (itoa no) " DWGNO_FIX=" (itoa nd)) f)
      (close f)))
  (princ))
