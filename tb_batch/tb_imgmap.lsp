(defun im:pos (pat s / i m r)
  (setq m (strlen pat) i 1)
  (while (and (not r) (<= (+ i m -1) (strlen s)))
    (if (= (substr s i m) pat) (setq r i))
    (setq i (1+ i)))
  r)
(defun im:base (p / i r)
  (setq i (strlen p))
  (while (and (> i 0) (not r))
    (if (member (substr p i 1) '("\\" "/")) (setq r (substr p (1+ i))))
    (setq i (1- i)))
  (if r r p))
(defun im:token (s / u i j c r)
  (setq u (strcase s))
  (cond
    ((setq i (im:pos "1010001-" u))
     (setq u (substr u (+ i 8)) j 1 r "")
     (while (and (<= j (strlen u)) (not (member (setq c (substr u j 1)) '("_" "-" "."))))
       (setq r (strcat r c) j (1+ j)))
     r)
    ((im:pos "DCLOGO" u) "DCLOGO")
    ((im:pos "EGISLOGO" u) "EGISLOGO")
    ((im:pos "RTCC" u) "RTCC")
    ((im:pos "LVI" u) "LVI")))
(defun c:TBIMGMAP (/ map d nm ed p tok hit nf nu miss f)
  (foreach fl *IM-FILES*
    (if (setq tok (im:token fl)) (setq map (cons (cons tok fl) map))))
  (setq nf 0 nu 0 miss "")
  (if (setq d (dictsearch (namedobjdict) "ACAD_IMAGE_DICT"))
    (foreach g d
      (cond ((= (car g) 3) (setq nm (cdr g)))
            ((= (car g) 350)
             (setq ed (entget (cdr g)) p (cdr (assoc 1 ed)))
             (if (not (and p (> (strlen p) 0) (findfile p)))
               (progn
                 (setq tok (im:token nm))
                 (if (and (not tok) p (> (strlen p) 0)) (setq tok (im:token (im:base p))))
                 (if (and tok (setq hit (cdr (assoc tok map))))
                   (progn
                     (if p
                       (entmod (subst (cons 1 (strcat *IM-DIR* hit)) (assoc 1 ed) ed))
                       (entmod (append ed (list (cons 1 (strcat *IM-DIR* hit))))))
                     (setq nf (1+ nf)))
                   (setq nu (1+ nu) miss (strcat miss " [" nm "]")))))))))
  (if (setq f (open *IM-LOG* "a"))
    (progn (write-line (strcat (getvar "DWGNAME") ",RELINKED=" (itoa nf) " UNMATCHED=" (itoa nu) "," miss) f) (close f)))
  (princ))
