(setq *ST-NEW* "100% DETAILED DESIGN"
      *ST-LOG* "C:/RevitAddinDev/CIVIL 3D_MCP Setup/tb_batch/tb_stage_log.csv")
(defun st:txt (e) (cdr (assoc 1 (entget e))))
(defun st:y (e) (cadr (cdr (assoc 10 (entget e)))))
(defun st:ss->list (ss / i l)
  (if ss (progn (setq i 0) (repeat (sslength ss) (setq l (cons (ssname ss i) l) i (1+ i)))))
  l)
(defun st:fix (ents / hy n ed)
  (setq n 0 hy nil)
  (foreach e ents (if (= (st:txt e) "REV") (setq hy (st:y e))))
  (foreach e ents
    (if (and (wcmatch (strcase (st:txt e)) "*SCHEMATIC DESIGN*")
             (or (not hy) (< (st:y e) hy)))
      (progn
        (setq ed (entget e))
        (entmod (subst (cons 1 *ST-NEW*) (assoc 1 ed) ed))
        (entupd e)
        (setq n (1+ n)))))
  n)
(defun st:blk-mtext (bn / sub l)
  (setq sub (cdr (assoc -2 (entget (tblobjname "BLOCK" bn)))))
  (while sub
    (if (= (cdr (assoc 0 (entget sub))) "MTEXT") (setq l (cons sub l)))
    (setq sub (entnext sub)))
  l)
(defun c:TBSTAGE (/ n bl bn f *error*)
  (defun *error* (msg / ef)
    (if (setq ef (open *ST-LOG* "a"))
      (progn (write-line (strcat (getvar "DWGNAME") ",LISP_ERROR " msg) ef) (close ef)))
    (princ))
  (setq n (st:fix (st:ss->list (ssget "_X" '((0 . "MTEXT") (67 . 1))))))
  (foreach e (st:ss->list (ssget "_X" '((0 . "INSERT") (67 . 1))))
    (setq bn (cdr (assoc 2 (entget e))))
    (if (not (member bn bl))
      (progn (setq bl (cons bn bl)) (setq n (+ n (st:fix (st:blk-mtext bn)))))))
  (if (setq f (open *ST-LOG* "a"))
    (progn (write-line (strcat (getvar "DWGNAME") ",CHANGED=" (itoa n)) f) (close f)))
  (princ (strcat "\nTBSTAGE changed " (itoa n)))
  (princ))
