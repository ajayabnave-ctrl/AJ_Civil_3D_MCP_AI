(setq *AU-LOG* "C:/RevitAddinDev/CIVIL 3D_MCP Setup/tb_batch/tb_audit.csv")
(defun au:trim (s)
  (while (and (> (strlen s) 0) (= (substr s 1 1) " ")) (setq s (substr s 2)))
  (while (and (> (strlen s) 0) (= (substr s (strlen s) 1) " ")) (setq s (substr s 1 (1- (strlen s)))))
  s)
(defun au:strip (s / i n c r nx)
  (setq i 1 n (strlen s) r "")
  (while (<= i n)
    (setq c (substr s i 1))
    (cond
      ((or (= c "{") (= c "}")) (setq i (1+ i)))
      ((= c "\\")
       (setq nx (substr s (1+ i) 1))
       (cond
         ((= nx "P") (setq r (strcat r " ") i (+ i 2)))
         ((member nx '("L" "l" "O" "o" "K" "k")) (setq i (+ i 2)))
         ((member nx '("\\" "{" "}")) (setq r (strcat r nx) i (+ i 2)))
         ((= nx "U") (setq r (strcat r "'") i (+ i 7)))
         (T (setq i (+ i 2))
            (while (and (<= i n) (/= (substr s i 1) ";")) (setq i (1+ i)))
            (setq i (1+ i)))))
      (T (setq r (strcat r c) i (1+ i)))))
  (au:trim r))
(defun au:ss->list (ss / i l)
  (if ss (progn (setq i 0) (repeat (sslength ss) (setq l (cons (ssname ss i) l) i (1+ i)))))
  l)
(defun au:items (/ l ed p ins bn sub sed q done)
  (foreach e (au:ss->list (ssget "_X" '((0 . "MTEXT,TEXT") (67 . 1))))
    (setq ed (entget e) p (cdr (assoc 10 ed)))
    (setq l (cons (list e (au:strip (cdr (assoc 1 ed))) (car p) (cadr p) (cdr (assoc 8 ed)) "PS" (cdr (assoc 1 ed))) l)))
  (foreach e (au:ss->list (ssget "_X" '((0 . "INSERT") (67 . 1))))
    (setq ed (entget e) bn (cdr (assoc 2 ed)) ins (cdr (assoc 10 ed)))
    (if (not (member bn done))
      (progn
        (setq done (cons bn done))
        (setq sub (cdr (assoc -2 (entget (tblobjname "BLOCK" bn)))))
        (while sub
          (setq sed (entget sub))
          (if (member (cdr (assoc 0 sed)) '("MTEXT" "TEXT"))
            (progn
              (setq q (cdr (assoc 10 sed)))
              (setq l (cons (list sub (au:strip (cdr (assoc 1 sed))) (+ (car q) (car ins)) (+ (cadr q) (cadr ins)) (cdr (assoc 8 sed)) (strcat "BLK:" bn) (cdr (assoc 1 sed))) l))))
          (setq sub (entnext sub))))))
  l)
(defun au:datep (s) (wcmatch s "##.##.##,##.##.####"))
(defun au:classify (/ items dn hdr dte dx dy cls out xr yh xd)
  (setq items (au:items))
  (foreach it items
    (cond ((and (not dn) (wcmatch (nth 1 it) "NC-CQT-###-####-RTC-DWG-LI-*")) (setq dn it))
          ((= (nth 1 it) "REV") (setq hdr it))
          ((= (nth 1 it) "DATE") (setq dte it))))
  (if hdr (setq xr (nth 2 hdr) yh (nth 3 hdr) xd (if dte (nth 2 dte) (+ xr 110.0))))
  (foreach it items
    (setq cls nil)
    (if dn (setq dx (- (nth 2 it) (nth 2 dn)) dy (- (nth 3 it) (nth 3 dn))))
    (cond
      ((and dn (wcmatch (nth 1 it) "@") (> dx 70.0) (< dx 115.0) (> dy 4.0) (< dy 14.0)) (setq cls "REVNO"))
      ((and dn (au:datep (nth 1 it)) (> dx 75.0) (< dx 115.0) (> dy 40.0) (< dy 52.0)) (setq cls "SEALDATE"))
      ((and hdr (> (nth 2 it) (- xr 10.0)) (< (nth 2 it) (+ xd 30.0)) (> (nth 3 it) yh) (< (nth 3 it) (+ yh 40.0)))
       (setq cls (if (= (substr (nth 5 it) 1 3) (substr (nth 5 hdr) 1 3)) "REVROW" "REVROW_OVERLAY")))
      ((au:datep (nth 1 it)) (setq cls "OTHERDATE")))
    (if cls (setq out (cons (cons cls it) out))))
  (list dn hdr out))
(defun c:TBAUDIT (/ r f dn)
  (setq r (au:classify) dn (car r))
  (setq f (open *AU-LOG* "a"))
  (write-line (strcat (getvar "DWGNAME") "|INFO|" (if dn (strcat "DWGNO=" (nth 1 dn)) "NO_DWGNO") "|" (if (cadr r) (strcat "REVHDR_IN=" (nth 5 (cadr r))) "NO_REVHDR")) f)
  (foreach o (reverse (caddr r))
    (write-line (strcat (getvar "DWGNAME") "|" (car o) "|" (nth 6 o) "|" (nth 5 o) "|" (rtos (nth 3 o) 2 2) "," (rtos (nth 4 o) 2 2) "|" (nth 2 o) "|" (nth 7 o)) f))
  (close f)
  (princ))
