(setq *TB-SRCDIR* nil)
(setq *TB-KEEP*    2
      *TB-LAYER*   "Z-000-P_SCHED,G-ANNO-SCHD"
      *TB-TBLAYER* "Z-020-M_TITLE_BLOCK,G-ANNO-TTLB"
      *TB-LOG*     "C:/RevitAddinDev/CIVIL 3D_MCP Setup/tb_batch/tb_batch_log.csv")
(defun tb:txt (e) (cdr (assoc 1 (entget e))))
(defun tb:x   (e) (car  (cdr (assoc 10 (entget e)))))
(defun tb:y   (e) (cadr (cdr (assoc 10 (entget e)))))
(defun tb:settxt (e s / ed)
  (setq ed (entget e))
  (entmod (subst (cons 1 s) (assoc 1 ed) ed))
  (entupd e))
(defun tb:movey (e dy / ed p)
  (setq ed (entget e) p (cdr (assoc 10 ed)))
  (entmod (subst (cons 10 (list (car p) (+ (cadr p) dy) (if (caddr p) (caddr p) 0.0)))
                 (assoc 10 ed) ed))
  (entupd e))
(defun tb:ss->list (ss / i l)
  (if ss (progn (setq i 0) (repeat (sslength ss) (setq l (cons (ssname ss i) l) i (1+ i)))))
  l)
(defun tb:by-layout (ents / al k)
  (foreach e ents
    (setq k (cdr (assoc 410 (entget e))))
    (if (assoc k al)
      (setq al (subst (cons k (cons e (cdr (assoc k al)))) (assoc k al) al))
      (setq al (cons (list k e) al))))
  al)
(defun tb:process-layout (ents tbents inblk / s hdr dte xr yh xmax lets n pitch tol ybot old kept
                                       i yl row newrev cnt oldrev)
  (foreach e ents
    (cond ((= (tb:txt e) "REV")  (setq hdr e))
          ((= (tb:txt e) "DATE") (setq dte e))))
  (if (not hdr)
    "NO_REV_HEADER"
    (progn
      (setq xr (tb:x hdr) yh (tb:y hdr)
            xmax (if dte (+ (tb:x dte) 30.0) (+ xr 200.0)))
      (foreach e ents
        (if (and (wcmatch (tb:txt e) "@")
                 (< (abs (- (tb:x e) xr)) 6.0)
                 (> (tb:y e) yh))
          (setq lets (cons e lets))))
      (setq lets (vl-sort lets '(lambda (a b) (< (tb:y a) (tb:y b))))
            n (length lets))
      (cond
        ((<= n *TB-KEEP*) (strcat "SKIPPED_" (itoa n) "_ROWS"))
        (T
         (setq oldrev (tb:txt (last lets)))
         (setq pitch (- (tb:y (cadr lets)) (tb:y (car lets)))
               tol   (* 0.4 (abs pitch))
               ybot  (tb:y (car lets))
               i 0)
         (foreach l lets
           (setq yl (tb:y l) row nil)
           (foreach e ents
             (if (and (entget e)
                      (< (abs (- (tb:y e) yl)) tol)
                      (>= (tb:x e) (- xr 8.0)) (<= (tb:x e) xmax))
               (setq row (cons e row))))
           (if (< i (- n *TB-KEEP*))
             (foreach e row (if inblk (tb:settxt e "") (entdel e)))
             (progn
               (setq cnt (- i (- n *TB-KEEP*))
                     newrev (chr (+ 65 cnt)))
               (tb:settxt l newrev)
               (foreach e row (tb:movey e (- (+ ybot (* cnt pitch)) yl)))))
           (setq i (1+ i)))
         (foreach e tbents
           (if (entget e)
             (progn
               (setq s (tb:txt e))
               (if (and (> (strlen s) 0) (= (substr s (strlen s)) oldrev))
                 (cond ((= s oldrev) (tb:settxt e newrev))
                       ((wcmatch s "\\[fp]*;@") (tb:settxt e (strcat (substr s 1 (1- (strlen s))) newrev))))))))
         (strcat "OK:" newrev))))))
(defun tb:fiximages (/ d n ed p)
  (setq n 0)
  (if (and *TB-SRCDIR* (setq d (dictsearch (namedobjdict) "ACAD_IMAGE_DICT")))
    (foreach g d
      (if (= (car g) 350)
        (progn
          (setq ed (entget (cdr g)) p (cdr (assoc 1 ed)))
          (if (and p (> (strlen p) 2)
                   (/= (substr p 2 1) ":")
                   (/= (substr p 1 2) "\\\\"))
            (progn
              (if (= (substr p 1 2) ".\\") (setq p (substr p 3)))
              (entmod (subst (cons 1 (strcat *TB-SRCDIR* p)) (assoc 1 ed) ed))
              (setq n (1+ n))))))))
  n)
(defun tb:ps-blocknames (/ l n)
  (foreach e (tb:ss->list (ssget "_X" '((0 . "INSERT") (67 . 1))))
    (setq n (cdr (assoc 2 (entget e))))
    (if (not (member n l)) (setq l (cons n l))))
  l)
(defun tb:blk-mtext (bn / sub l)
  (setq sub (cdr (assoc -2 (entget (tblobjname "BLOCK" bn)))))
  (while sub
    (if (= (cdr (assoc 0 (entget sub))) "MTEXT") (setq l (cons sub l)))
    (setq sub (entnext sub)))
  l)
(defun tb:ps-revno-cands (/ l)
  (foreach e (tb:ss->list (ssget "_X" '((0 . "MTEXT") (67 . 1))))
    (if (wcmatch (tb:txt e) "\\[fp]*;@") (setq l (cons e l))))
  l)
(defun c:TBREVB (/ al tbal res r f newrev ni bents *error*)
  (defun *error* (msg / ef)
    (if (setq ef (open *TB-LOG* "a"))
      (progn (write-line (strcat (getvar "DWGPREFIX") (getvar "DWGNAME") ",LISP_ERROR " msg ",") ef) (close ef)))
    (princ))
  (setq al   (tb:by-layout (tb:ss->list (ssget "_X" (list '(0 . "MTEXT") (cons 8 *TB-LAYER*) '(67 . 1)))))
        tbal (tb:by-layout (tb:ss->list (ssget "_X" (list '(0 . "MTEXT") (cons 8 *TB-TBLAYER*) '(67 . 1))))))
  (foreach lay al
    (setq r (tb:process-layout (cdr lay) (cdr (assoc (car lay) tbal)) nil))
    (if (wcmatch r "OK:*") (setq newrev (substr r 4)))
    (setq res (if res (strcat res " / " (car lay) "=" r) (strcat (car lay) "=" r))))
  (foreach bn (tb:ps-blocknames)
    (setq bents (tb:blk-mtext bn))
    (if (and (vl-some '(lambda (e) (= (tb:txt e) "REV")) bents)
             (vl-some '(lambda (e) (= (tb:txt e) "DESCRIPTION")) bents))
      (progn
        (setq r (tb:process-layout bents (append bents (tb:ps-revno-cands)) T))
        (if (wcmatch r "OK:*") (setq newrev (substr r 4)))
        (setq res (if res (strcat res " / BLOCK " bn "=" r) (strcat "BLOCK " bn "=" r))))))
  (if (not res) (setq res "NO_REV_TEXT"))
  (if newrev (progn (setq ni (tb:fiximages)) (setq res (strcat res " IMGPATHS_FIXED=" (itoa ni)))))
  (if (setq f (open *TB-LOG* "a"))
    (progn
      (write-line (strcat (getvar "DWGPREFIX") (getvar "DWGNAME") "," res "," (if newrev newrev "")) f)
      (close f)))
  (princ (strcat "\nTBREVB: " res))
  (princ))
(princ "\nTBREVB loaded. Type TBREVB to run.")
(princ)
